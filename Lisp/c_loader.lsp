(princ "Loading TRUSS-PY functions and commands ...\n")
(vl-load-com)
(load "f_functions")
(load "c_define_elements")
(load "c_define_supports")
(load "c_define_loads")
(load "c_export_model")
(load "c_draw_forces")
(load "c_draw_displacements")
(load "c_draw_geometry")
(load "c_draw_reactions")
(load "c_draw_stresses")
(princ "OK")
